;;; ============================================================================
;;; levantamento_postes.lsp - Levantamento de Postes e Clientes no DWG
;;; Comandos: LEVANTAR_POSTES, LP
;;; Coleta TEXT/MTEXT por ponto, calcula clientes, posições e CS,
;;; e gera tabela nativa do AutoCAD com persistência isolada por DWG (LData).
;;; ============================================================================
(vl-load-com)
(if (null fboundp) (defun fboundp (s) (and s (boundp s) (member (type (eval s)) '(SUBR USUBR)))))
(foreach m '("clandestino_light" "clandestino_topologia")
  (setq *lp-clan-carregado* nil)
  (foreach p (list (strcat m ".lsp") (strcat "orcamento\\" m ".lsp") (strcat "C:\\Users\\jonat\\OneDrive - IM3 Brasil\\aux cad\\orcamento\\" m ".lsp"))
    (if (and (null *lp-clan-carregado*) (findfile p)) (progn (vl-catch-all-apply 'load (list (findfile p))) (setq *lp-clan-carregado* t)))))
;;; ----------------------------------------------------------------------------
;;; 1. UTILITÁRIOS DE STRING E SANITIZAÇÃO DE TEXTO
;;; ----------------------------------------------------------------------------
(defun lp-trim (value) (if (= (type value) 'STR) (vl-string-trim " \t\r\n{}" value) ""))
(defun lp-strip-mtext (value / index len char next end result)
  "Remove códigos de formatação MText mantendo quebras de linha normalizadas."
  (if (not (= (type value) 'STR)) ""
    (progn
      (setq index 1 len (strlen value) result "")
      (while (<= index len)
        (setq char (substr value index 1))
        (cond
          ((or (= char "{") (= char "}")) (setq index (1+ index)))
          ((= char "\\")
           (setq next (if (< index len) (substr value (1+ index) 1) ""))
           (cond
             ((or (= (strcase next) "P") (= next "~"))
              (setq result (strcat result "\n") index (+ index 2)))
             (t
              (setq end (+ index 1))
              (while (and (<= end len) (/= (substr value end 1) ";")) (setq end (1+ end)))
              (setq index (if (<= end len) (1+ end) (+ index 2))))))
          (t (setq result (strcat result char) index (1+ index)))))
      (lp-trim result))))
(defun lp-split-lines (text / len idx char line lines)
  "Divide uma string contendo quebras de linha em uma lista de linhas."
  (setq len (strlen text) idx 1 line "" lines '())
  (while (<= idx len)
    (setq char (substr text idx 1))
    (if (or (= char "\n") (= char "\r"))
      (progn
        (if (/= (lp-trim line) "") (setq lines (append lines (list (lp-trim line)))))
        (setq line "")
        (if (and (< idx len)
                 (or (and (= char "\r") (= (substr text (1+ idx) 1) "\n"))
                     (and (= char "\n") (= (substr text (1+ idx) 1) "\r"))))
          (setq idx (1+ idx))))
      (setq line (strcat line char)))
    (setq idx (1+ idx)))
  (if (/= (lp-trim line) "") (setq lines (append lines (list (lp-trim line)))))
  lines)
;;; ----------------------------------------------------------------------------
;;; 2. FILTRAGEM DE RUÍDO E TEXTOS AUXILIARES
;;; ----------------------------------------------------------------------------
(defun lp-is-noise-line (line / upper)
  "Verifica se a linha contém dados auxiliares (esforço daN, demanda, etc.)."
  (setq upper (strcase (lp-trim line)))
  (or (= upper "") (vl-string-search "DAN" upper) (vl-string-search "ESF. RES" upper)
      (vl-string-search "ESF." upper) (vl-string-search "ESFORCO" upper)
      (vl-string-search "DEM.:" upper) (vl-string-search "DEM." upper)
      (vl-string-search "DEMANDA" upper) (vl-string-search "ACUM.:" upper)
      (vl-string-search "ACUM." upper) (vl-string-search "ACUMULADO" upper)
      (vl-string-search "KVA" upper) (vl-string-search "CLIENTE" upper)))
(defun lp-format-val (val)
  "Formata valor para exibição em tabelas e console."
  (cond
    ((numberp val) (itoa val))
    ((= (type val) 'STR) val)
    (t "-")))
;;; ----------------------------------------------------------------------------
;;; 3. PARSERS MODULARES
;;; ----------------------------------------------------------------------------
;; 3.1 Parser de Código de Poste
(defun lp-parse-poste (lines / item found upper len i ch all-digits)
  "Localiza e extrai o código do poste (ex: P112600B, P212600B, P01)."
  (setq found nil)
  (foreach item lines
    (if (not found)
      (progn
        (setq upper (strcase (lp-trim item)))
        (if (and (not (lp-is-noise-line upper))
                 (>= (strlen upper) 2)
                 (= (substr upper 1 1) "P"))
          (progn
            (setq ch (substr upper 2 1))
            ;; O segundo caractere deve ser dígito ou traço seguido de dígito
            (if (or (and (>= (ascii ch) 48) (<= (ascii ch) 57))
                    (= ch "-"))
              (setq found upper)))))))
  found)
;; 3.2 Parser de Ramais e Clientes
(defun lp-parse-phase-qty (token / up x-pos qty phase)
  "Extrai (quantidade fase) de um token como 12x1ø ou 1x3%%c."
  (setq up (strcase (lp-trim token)))
  (setq x-pos (vl-string-search "X" up))
  (if x-pos
    (progn
      (setq qty (atoi (substr up 1 x-pos)))
      (cond
        ((or (vl-string-search "3" (substr up (+ x-pos 2)))
             (vl-string-search "TRI" up))
         (setq phase 3))
        ((or (vl-string-search "2" (substr up (+ x-pos 2)))
             (vl-string-search "BI" up))
         (setq phase 2))
        (t
         (setq phase 1)))
      (if (> qty 0) (list qty phase) nil))
    nil))
(defun lp-parse-ramais-e-clientes (lines / ramais-found mono-qty bi-qty tri-qty
                                          ramal-str upper parts tokens token pq)
  "Extrai ramais normalizados, total de clientes e contagem por fase exclusivamente dos ramais."
  (setq mono-qty 0
        bi-qty 0
        tri-qty 0
        ramais-found '())
  (foreach line lines
    (setq upper (strcase (lp-trim line)))
    (if (not (lp-is-noise-line upper))
      (progn
        ;; Detecção de ramais por fase (ex: 12x1ø | 1x3ø ou 12x%%C1)
        (if (or (vl-string-search "X1" upper)
                (vl-string-search "X2" upper)
                (vl-string-search "X3" upper)
                (vl-string-search "Ø" upper)
                (vl-string-search "ø" line)
                (vl-string-search "%%C" upper))
          (progn
            ;; Divide tokens por separadores comuns: barra vertical, vírgula, mais
            (setq parts (vl-string-translate "|,+" "   " upper))
            (setq tokens (lp-split-lines (vl-string-translate " " "\n" parts)))
            (foreach token tokens
              (setq pq (lp-parse-phase-qty token))
              (if pq
                (cond
                  ((= (cadr pq) 1)
                   (setq mono-qty (+ mono-qty (car pq))))
                  ((= (cadr pq) 2)
                   (setq bi-qty (+ bi-qty (car pq))))
                  ((= (cadr pq) 3)
                   (setq tri-qty (+ tri-qty (car pq))))))))))))
  ;; Monta representação normalizada com %%C (ex: 12x%%C1 | 1x%%C3)
  (if (> mono-qty 0)
    (setq ramais-found (append ramais-found (list (strcat (itoa mono-qty) "x%%C1")))))
  (if (> bi-qty 0)
    (setq ramais-found (append ramais-found (list (strcat (itoa bi-qty) "x%%C2")))))
  (if (> tri-qty 0)
    (setq ramais-found (append ramais-found (list (strcat (itoa tri-qty) "x%%C3")))))
  (setq ramal-str "")
  (if ramais-found
    (progn
      (setq ramal-str (car ramais-found))
      (foreach item (cdr ramais-found)
        (setq ramal-str (strcat ramal-str " | " item)))))
  ;; Se não há ramais identificados, clientes é '-'
  (if (null ramais-found)
    (list "-" "-" 0 0 0)
    (list ramal-str (+ mono-qty bi-qty tri-qty) mono-qty bi-qty tri-qty)))
;; 3.3 Parser de Luminária
(defun lp-parse-luminaria (lines / lum upper)
  "Extrai identificação de luminária (ex: IP, LUM., LED, etc.) ou '-'."
  (setq lum "-")
  (foreach line lines
    (if (= lum "-")
      (progn
        (setq upper (strcase (lp-trim line)))
        (if (and (not (lp-is-noise-line upper))
                 (or (vl-string-search "IP" upper)
                     (vl-string-search "LUM" upper)
                     (vl-string-search "LED" upper)
                     (vl-string-search "PÉTALA" upper)
                     (vl-string-search "PETALA" upper)
                     (and (vl-string-search "W" upper)
                          (or (vl-string-search "70" upper)
                              (vl-string-search "100" upper)
                              (vl-string-search "150" upper)
                              (vl-string-search "250" upper)))))
          (setq lum (lp-trim line))))))
  lum)
;; 3.4 Parsers de Demanda e Demanda Acumulada
(defun lp-extract-value-after-key (text key / up pos len idx ch val has-digit)
  "Extrai o valor numérico após uma chave (ex: 'DEM' ou 'ACUM') preservando decimais."
  (setq up (strcase text) pos (vl-string-search key up))
  (if pos
    (progn
      (setq len (strlen text) idx (+ pos (strlen key) 1) val "" has-digit nil)
      (while (and (<= idx len) (member (substr up idx 1) '("." ":" " " "-" "=" "\t")))
        (setq idx (1+ idx)))
      (while (and (<= idx len)
                  (or (and (>= (ascii (substr text idx 1)) 48) (<= (ascii (substr text idx 1)) 57))
                      (= (substr text idx 1) ",") (= (substr text idx 1) ".")))
        (setq ch (substr text idx 1))
        (if (and (>= (ascii ch) 48) (<= (ascii ch) 57)) (setq has-digit t))
        (setq val (strcat val ch) idx (1+ idx)))
      (while (and (> (strlen val) 0) (or (= (substr val (strlen val) 1) ".") (= (substr val (strlen val) 1) ",")))
        (setq val (substr val 1 (1- (strlen val)))))
      (if (and has-digit (> (strlen val) 0)) val nil))
    nil))
(defun lp-extract-demanda-line (line / upper)
  "Tenta extrair valor de Demanda da linha."
  (setq upper (strcase (lp-trim line)))
  (vl-some '(lambda (p) (if (vl-string-search p upper) (lp-extract-value-after-key line p)))
           '("DEMANDA" "DEM.:" "DEM:" "DEM." "DEM")))
(defun lp-parse-demanda (lines / found-val ambig item candidate)
  "Extrai o valor de Demanda (kVA) preservando formato, ou '-' se ausente/ambíguo."
  (setq found-val nil ambig nil)
  (foreach item lines
    (if (setq candidate (lp-extract-demanda-line item))
      (if (null found-val) (setq found-val candidate)
        (if (/= found-val candidate) (setq ambig t)))))
  (if (or (null found-val) ambig) "-" found-val))
(defun lp-extract-acumulada-line (line / upper)
  "Tenta extrair valor de Demanda Acumulada da linha."
  (setq upper (strcase (lp-trim line)))
  (vl-some '(lambda (p) (if (vl-string-search p upper) (lp-extract-value-after-key line p)))
           '("ACUMULADA" "ACUMULADO" "ACUM.:" "ACUM:" "ACUM." "ACUM")))
(defun lp-parse-acumulada (lines / found-val ambig item candidate)
  "Extrai o valor de Demanda Acumulada (kVA) preservando formato, ou '-' se ausente/ambíguo."
  (setq found-val nil ambig nil)
  (foreach item lines
    (if (setq candidate (lp-extract-acumulada-line item))
      (if (null found-val) (setq found-val candidate)
        (if (/= found-val candidate) (setq ambig t)))))
  (if (or (null found-val) ambig) "-" found-val))
;; 3.5 Extrator de Coordenadas do Bloco CO
;; A rotina ADDBLOCO (topografia/addbloco.lsp) preenche exatamente os atributos
;; N e E do bloco CO como N=Y e E=X, já formatados com duas casas.  Esta rotina
;; reutiliza essa fonte persistida; nunca infere coordenadas pelo ponto local.
(defun lp-coord-numero-valido (value / clean normalized number index char dots digits valid)
  "Converte valor de atributo CO em número positivo, aceitando vírgula decimal."
  (setq clean (lp-trim value))
  (if (and (>= (strlen clean) 2)
           (or (= (strcase (substr clean 1 2)) "N:")
               (= (strcase (substr clean 1 2)) "E:")))
    (setq clean (lp-trim (substr clean 3))))
  (setq normalized (vl-string-translate "," "." clean)
        index 1
        dots 0
        digits 0
        valid (> (strlen normalized) 0))
  ;; ATOF aceita prefixos; por isso valida a string inteira antes de aceitá-la.
  (while (and valid (<= index (strlen normalized)))
    (setq char (substr normalized index 1))
    (cond
      ((and (= index 1) (or (= char "+") (= char "-"))))
      ((and (>= (ascii char) 48) (<= (ascii char) 57))
       (setq digits (1+ digits)))
      ((= char ".")
       (setq dots (1+ dots))
       (if (> dots 1) (setq valid nil)))
      (t (setq valid nil)))
    (setq index (1+ index)))
  (setq number (if valid (atof normalized) 0.0))
  (if (and valid (> digits 0) (> (abs number) 0.0001))
    number
    nil))
(defun lp-extrair-coordenadas-bloco (ent / edata tip obj has-atts atts-result atts-list tag val-n val-e n e)
  "Lê N/E do mecanismo CO; retorna '-' quando o bloco não traz coordenadas válidas."
  (if (or (null ent) (not (listp (setq edata (entget ent)))))
    "-"
    (progn
      (setq tip (cdr (assoc 0 edata)))
      (if (/= tip "INSERT")
        "-"
        (progn
          (setq val-n nil
                val-e nil)
          ;; O contrato real do CO é formado pelos atributos N e E de ADDBLOCO.
          (setq obj (vl-catch-all-apply 'vlax-ename->vla-object (list ent))
                has-atts nil)
          (if (not (vl-catch-all-error-p obj))
            (setq has-atts
              (vl-catch-all-apply 'vlax-get-property (list obj 'HasAttributes))))
          (if (and has-atts (not (vl-catch-all-error-p has-atts))
                   (= has-atts :vlax-true))
            (progn
              (setq atts-result (vl-catch-all-apply 'vlax-invoke (list obj 'GetAttributes)))
              (if (not (vl-catch-all-error-p atts-result))
                (progn
                  (setq atts-list (vlax-safearray->list (vlax-variant-value atts-result)))
                  (foreach att atts-list
                    (setq tag (strcase (vla-get-TagString att)))
                    (cond
                      ((= tag "N")
                       (setq val-n (lp-trim (vla-get-TextString att))))
                      ((= tag "E")
                       (setq val-e (lp-trim (vla-get-TextString att))))))))))
          (setq n (lp-coord-numero-valido val-n)
                e (lp-coord-numero-valido val-e))
          (if (and n e)
            (strcat "N: " (rtos n 2 2) "\nE: " (rtos e 2 2))
            "-"))))))
;;; ----------------------------------------------------------------------------
;;; 4. CÁLCULO DE POSIÇÕES E CAIXAS DE SERVIÇO (CS)
;;; ----------------------------------------------------------------------------
(defun lp-calc-posicoes (mono bi tri)
  "Calcula Total de Posições = (1ø * 1) + (2ø * 2) + (3ø * 3)."
  (if (and (= mono 0) (= bi 0) (= tri 0))
    "-"
    (+ (* mono 1) (* bi 2) (* tri 3))))
(defun lp-calc-cs (posicoes)
  "Calcula Total CS = teto(posicoes / 9)."
  (if (or (not (numberp posicoes)) (<= posicoes 0))
    "-"
    (/ (+ posicoes 8) 9)))
;;; ----------------------------------------------------------------------------
;;; 5. PROCESSAMENTO DE UM PONTO
;;; ----------------------------------------------------------------------------
(defun lp-process-point-texts (raw-texts-list seq coords / lines poste ram-res
                                                          ramais clientes mono bi tri
                                                          lum posicoes cs dem acum)
  "Consolida os textos brutos de um ponto e retorna o registro estruturado com coordenadas."
  (setq lines '())
  (foreach txt raw-texts-list
    (setq lines (append lines (lp-split-lines (lp-strip-mtext txt)))))
  (setq poste (lp-parse-poste lines))
  (if (and (null poste) (fboundp 'lp-clan-parse-no-poste) (fboundp 'lp-db-obter-modo) (= (lp-db-obter-modo) "CLANDESTINO"))
    (setq poste (lp-clan-parse-no-poste lines)))
  (if (null poste) (setq poste "-"))
  (setq ram-res (lp-parse-ramais-e-clientes lines))
  (setq ramais   (nth 0 ram-res)
        clientes (nth 1 ram-res)
        mono     (nth 2 ram-res)
        bi       (nth 3 ram-res)
        tri      (nth 4 ram-res))
  (setq lum (lp-parse-luminaria lines))
  (setq posicoes (lp-calc-posicoes mono bi tri)
        cs (lp-calc-cs posicoes)
        dem (lp-parse-demanda lines)
        acum (lp-parse-acumulada lines))
  (if (and (fboundp 'lp-db-obter-modo) (= (lp-db-obter-modo) "CLANDESTINO"))
    (setq dem (lp-clan-format-num (lp-clan-calcular-demanda (lp-db-obter-area) (if (numberp clientes) clientes 0)) t)))
  (if (or (null coords) (= coords "")) (setq coords "-"))
  (list (cons "SEQ" seq) (cons "POSTE" poste) (cons "RAMAIS" ramais)
        (cons "LUM" lum) (cons "CLIENTES" clientes) (cons "POSICOES" posicoes)
        (cons "CS" cs) (cons "DEMANDA" dem) (cons "ACUMULADA" acum)
        (cons "COORDENADAS" coords)
        (cons "RAW" raw-texts-list)))
;;; ----------------------------------------------------------------------------
;;; 6. PERSISTÊNCIA ISOLADA POR DWG (AutoCAD LData)
;;; ----------------------------------------------------------------------------
(setq *lp-dict-name* "OXCAD_LEVANTAMENTO")
(setq *lp-key-name* "PONTOS" *lp-key-tabela* "TABELA_HANDLE")
(defun lp-db-obter-pontos (/ dados)
  "Lê os pontos armazenados no LData do DWG ativo."
  (setq dados (vlax-ldata-get *lp-dict-name* *lp-key-name*))
  (if (listp dados) dados '()))
(defun lp-db-salvar-pontos (pontos)
  "Salva a lista de pontos no LData do DWG ativo."
  (vlax-ldata-put *lp-dict-name* *lp-key-name* pontos))
(defun lp-db-limpar-pontos ()
  "Remove a lista de pontos do LData do DWG ativo."
  (vlax-ldata-delete *lp-dict-name* *lp-key-name*))
(defun lp-db-obter-tabela-handle ()
  "Recupera o handle da tabela associada ao levantamento no DWG."
  (vlax-ldata-get *lp-dict-name* *lp-key-tabela*))
(defun lp-db-salvar-tabela-handle (handle)
  "Salva o handle da tabela associada no LData do DWG."
  (vlax-ldata-put *lp-dict-name* *lp-key-tabela* handle))
(defun lp-db-remover-tabela-handle ()
  "Remove o vínculo com a tabela no LData do DWG."
  (vlax-ldata-delete *lp-dict-name* *lp-key-tabela*))

;;; ----------------------------------------------------------------------------
;;; 7. GERAÇÃO DA TABELA NATIVA DO AUTOCAD
;;; ----------------------------------------------------------------------------

(defun lp-gerar-tabela-cad (pontos / acad doc space pt row-count col-count table
                                    row-idx p seq poste ramais lum clientes pos cs
                                    dem acum coords table-res fill-res)
  "Insere a tabela nativa de 10 colunas no desenho ativo com proteção transacional."
  (if (or (null pontos) (= (length pontos) 0))
    (progn
      (princ "\n[LEVANTAR_POSTES] Nenhum ponto coletado para gerar tabela.")
      nil)
    (progn
      (setq pt (getpoint "\nPonto de inserção da tabela de postes e clientes: "))
      (if (null pt)
        (progn
          (princ "\n[LEVANTAR_POSTES] Inserção cancelada pelo usuário. Coleta mantida.")
          nil)
        (if (and (fboundp 'lp-cqt-colunas-adicionais-p) (lp-cqt-colunas-adicionais-p)
                 (fboundp 'lp-cqt-gerar-tabela-cad))
          (lp-cqt-gerar-tabela-cad pontos pt)
          (progn
            (setq acad (vlax-get-acad-object)
                  doc  (vla-get-ActiveDocument acad)
                  space (vla-get-Block (vla-get-ActiveLayout doc))
                  row-count (+ 2 (length pontos))
                  col-count 10)
            (setq table-res
              (vl-catch-all-apply
                'vla-AddTable
                (list space (vlax-3d-point pt) row-count col-count 6.0 35.0)))
            (if (vl-catch-all-error-p table-res)
              (progn
                (princ (strcat "\n[LEVANTAR_POSTES][ERRO] Falha ao criar tabela: "
                               (vl-catch-all-error-message table-res)))
                (princ "\n[LEVANTAR_POSTES] A coleta foi preservada no DWG.")
                nil)
              (progn
                (setq table table-res)
                (setq fill-res
                  (vl-catch-all-apply
                    '(lambda ()
                       (vla-put-Layer table "0")
                       (vla-MergeCells table 0 0 0 9)
                       (vla-SetText table 0 0 "LEVANTAMENTO DE POSTES E CLIENTES")
                       (vla-SetText table 1 0 "PONTO")
                       (vla-SetText table 1 1 "POSTE")
                       (vla-SetText table 1 2 "RAMAIS")
                       (vla-SetText table 1 3 "LUMINÁRIA")
                       (vla-SetText table 1 4 "TOTAL CLIENTES")
                       (vla-SetText table 1 5 "TOTAL POSIÇÕES")
                       (vla-SetText table 1 6 "TOTAL CS")
                       (vla-SetText table 1 7 "DEMANDA (kVA)")
                       (vla-SetText table 1 8 "ACUMULADA (kVA)")
                       (vla-SetText table 1 9 "COORDENADAS")
                       (vla-SetColumnWidth table 0 22.0)
                       (vla-SetColumnWidth table 1 35.0)
                       (vla-SetColumnWidth table 2 50.0)
                       (vla-SetColumnWidth table 3 35.0)
                       (vla-SetColumnWidth table 4 38.0)
                       (vla-SetColumnWidth table 5 38.0)
                       (vla-SetColumnWidth table 6 25.0)
                       (vla-SetColumnWidth table 7 38.0)
                       (vla-SetColumnWidth table 8 38.0)
                       (vla-SetColumnWidth table 9 45.0)
                       (setq row-idx 2)
                       (foreach p pontos
                         (vla-SetText table row-idx 0 (lp-format-val (cdr (assoc "SEQ" p))))
                         (vla-SetText table row-idx 1 (lp-format-val (cdr (assoc "POSTE" p))))
                         (vla-SetText table row-idx 2 (lp-format-val (cdr (assoc "RAMAIS" p))))
                         (vla-SetText table row-idx 3 (lp-format-val (cdr (assoc "LUM" p))))
                         (vla-SetText table row-idx 4 (lp-format-val (cdr (assoc "CLIENTES" p))))
                         (vla-SetText table row-idx 5 (lp-format-val (cdr (assoc "POSICOES" p))))
                         (vla-SetText table row-idx 6 (lp-format-val (cdr (assoc "CS" p))))
                         (vla-SetText table row-idx 7 (lp-format-val (cdr (assoc "DEMANDA" p))))
                         (vla-SetText table row-idx 8 (lp-format-val (cdr (assoc "ACUMULADA" p))))
                         (vla-SetText table row-idx 9 (lp-format-val (cdr (assoc "COORDENADAS" p))))
                         (setq row-idx (1+ row-idx)))
                       (vla-Update table))))
                (if (vl-catch-all-error-p fill-res)
                  (progn
                    (princ (strcat "\n[LEVANTAR_POSTES][ERRO] Falha ao preencher células da tabela: "
                                   (vl-catch-all-error-message fill-res)))
                    (princ "\n[LEVANTAR_POSTES] A coleta foi preservada no DWG.")
                    nil)
                  (progn
                    (setq tbl-handle (vla-get-Handle table))
                    (lp-db-salvar-tabela-handle tbl-handle)
                    (princ (strcat "\n[LEVANTAR_POSTES] Tabela criada com sucesso com "
                                   (itoa (length pontos)) " pontos (Handle #" tbl-handle ")."))
                    table))))))))))

;;; ----------------------------------------------------------------------------
;;; 8. SINCRONIZAÇÃO ENTRE DESENHO E TABELA VINCULADA
;;; ----------------------------------------------------------------------------

(defun lp-validar-handle-texto (handle / ent edata tip)
  "Valida se o handle existe no DWG e é uma entidade de texto (TEXT ou MTEXT)."
  (if (or (null handle) (not (= (type handle) 'STR)) (= (lp-trim handle) ""))
    (list nil "Handle nulo ou inválido")
    (progn
      (setq ent (handent handle))
      (if (null ent)
        (list nil "Entidade não encontrada no desenho (excluída)")
        (progn
          (setq edata (entget ent))
          (if (or (null edata) (not (listp edata)))
            (list nil "Entidade apagada ou inacessível")
            (progn
              (setq tip (cdr (assoc 0 edata)))
              (if (not (member tip '("TEXT" "MTEXT")))
                (list nil (strcat "Tipo inválido (" tip "), esperado TEXT ou MTEXT"))
                (list t ent edata)))))))))

(defun lp-parse-num (str / clean num)
  "Converte string com vírgula ou ponto para número float, ou nil se inválido."
  (if (or (null str) (not (= (type str) 'STR)) (= str "-") (= str ""))
    nil
    (progn
      (setq clean (vl-string-translate "," "." (lp-trim str)))
      (setq num (read clean))
      (if (numberp num) (float num) nil))))

(defun lp-format-num (num use-comma / s)
  "Formata número float com duas casas decimais preservando pontuação."
  (if (null num)
    "-"
    (progn
      (setq s (rtos num 2 2))
      (if use-comma (vl-string-translate "." "," s) s))))

(defun lp-recalcular-demandas-acumuladas (pontos / novos acum-anterior p dem-str acum-str
                                                  dem-val acum-val use-comma novo-p pts-dem)
  "Recalcula a demanda acumulada em cadeia para os pontos quando aplicável."
  (if (and (fboundp 'lp-db-obter-modo) (= (lp-db-obter-modo) "CLANDESTINO"))
    (progn
      (setq pts-dem (lp-clan-recalcular-pontos pontos (lp-db-obter-area) (lp-db-obter-sentido)))
      (if (fboundp 'lp-cqt-calcular-rede-pontos) (lp-cqt-calcular-rede-pontos pts-dem) pts-dem))
    (progn
      (setq novos '()
            acum-anterior 0.0)
      (foreach p pontos
        (setq dem-str (cdr (assoc "DEMANDA" p))
              acum-str (cdr (assoc "ACUMULADA" p)))
        (setq dem-val (lp-parse-num dem-str))
        (setq use-comma (if (and dem-str (vl-string-search "," dem-str)) t nil))
        (if (and (null use-comma) acum-str (vl-string-search "," acum-str))
          (setq use-comma t))

        (if dem-val
          (if (or (= acum-str "-") (null acum-str)
                  (and (numberp (lp-parse-num acum-str)) (> acum-anterior 0.0)))
            (progn
              (setq acum-anterior (+ acum-anterior dem-val))
              (setq novo-p (subst (cons "ACUMULADA" (lp-format-num acum-anterior use-comma))
                                  (assoc "ACUMULADA" p)
                                  p)))
            (progn
              (setq acum-val (lp-parse-num acum-str))
              (if acum-val
                (setq acum-anterior acum-val)
                (setq acum-anterior (+ acum-anterior dem-val)))
              (setq novo-p p)))
          (setq novo-p p))
        (setq novos (append novos (list novo-p))))
      novos)))

(defun lp-atualizar-celulas-tabela (table pontos / row-idx rows-existentes rows-necessarias p col-idx)
  "Atualiza as células da tabela nativa existente sem recriá-la nem mover sua posição."
  (if (and (fboundp 'lp-cqt-colunas-adicionais-p) (lp-cqt-colunas-adicionais-p)
           (fboundp 'lp-cqt-atualizar-celulas-tabela))
    (lp-cqt-atualizar-celulas-tabela table pontos)
    (progn
      (setq rows-existentes (vla-get-Rows table)
            rows-necessarias (+ 2 (length pontos)))
      (if (> rows-necessarias rows-existentes)
        (vl-catch-all-apply 'vla-InsertRows
                            (list table rows-existentes 6.0 (- rows-necessarias rows-existentes))))
      (setq row-idx 2)
      (foreach p pontos
        (if (< row-idx (vla-get-Rows table))
          (progn
            (setq col-idx 0)
            (foreach k '("SEQ" "POSTE" "RAMAIS" "LUM" "CLIENTES" "POSICOES" "CS" "DEMANDA" "ACUMULADA" "COORDENADAS")
              (vla-SetText table row-idx col-idx (lp-format-val (cdr (assoc k p))))
              (setq col-idx (1+ col-idx)))))
        (setq row-idx (1+ row-idx)))
      (vla-Update table)
      t)))

(defun lp-sincronizar-levantamento (pontos tbl-handle / tbl-ent edata-tbl tbl-obj
                                                       tem-alteracao pontos-afetados
                                                       novos-pontos erro-msg
                                                       p seq handles raw-antigo
                                                       cur-raw h val-res cur-edata cur-txt
                                                       coords blk-h novo-p update-res)
  "Verifica referências no DWG, detecta mudanças e sincroniza a tabela existente."
  (if (or (null pontos) (= (length pontos) 0) (null tbl-handle))
    (list :nada-a-fazer pontos)
    (progn
      (setq tbl-ent (handent tbl-handle))
      (if (or (null tbl-ent)
              (not (listp (setq edata-tbl (entget tbl-ent))))
              (/= (cdr (assoc 0 edata-tbl)) "ACAD_TABLE"))
        (list :tabela-inexistente tbl-handle)
        (progn
          (setq tbl-obj (vl-catch-all-apply 'vlax-ename->vla-object (list tbl-ent)))
          (if (vl-catch-all-error-p tbl-obj)
            (list :erro (strcat "Falha ao obter objeto da tabela: "
                                (vl-catch-all-error-message tbl-obj)))
            (progn
              (setq tem-alteracao nil
                    pontos-afetados '()
                    novos-pontos '()
                    erro-msg nil)

              (foreach p pontos
                (if (null erro-msg)
                  (progn
                    (setq seq (cdr (assoc "SEQ" p))
                          handles (cdr (assoc "TEXT_HANDLES" p))
                          raw-antigo (cdr (assoc "RAW" p))
                          coords (cdr (assoc "COORDENADAS" p))
                          blk-h (cdr (assoc "BLOCO_POSTE_HANDLE" p)))

                    (if (or (null handles) (not (listp handles)))
                      (setq novos-pontos (append novos-pontos (list p)))
                      (progn
                        (setq cur-raw '())
                        (foreach h handles
                          (if (null erro-msg)
                            (progn
                              (setq val-res (lp-validar-handle-texto h))
                              (if (not (car val-res))
                                (setq erro-msg (strcat "Texto do Ponto " (itoa seq)
                                                       " (Handle #" h "): " (cadr val-res)))
                                (progn
                                  (setq cur-edata (caddr val-res))
                                  (setq cur-txt (cdr (assoc 1 cur-edata)))
                                  (setq cur-raw (append cur-raw (list (if cur-txt cur-txt "")))))))))

                        (if (null erro-msg)
                          (if (equal cur-raw raw-antigo)
                            (setq novos-pontos (append novos-pontos (list p)))
                            (progn
                              (setq tem-alteracao t
                                    pontos-afetados (append pontos-afetados (list seq)))
                              (setq novo-p (lp-process-point-texts cur-raw seq coords))
                              (setq novo-p (cons (cons "TEXT_HANDLES" handles) novo-p))
                              (if blk-h (setq novo-p (cons (cons "BLOCO_POSTE_HANDLE" blk-h) novo-p)))
                              (if (and (= (cdr (assoc "POSTE" novo-p)) "-")
                                       (cdr (assoc "POSTE" p))
                                       (/= (cdr (assoc "POSTE" p)) "-"))
                                (setq novo-p (subst (cons "POSTE" (cdr (assoc "POSTE" p)))
                                                    (assoc "POSTE" novo-p) novo-p)))
                              (setq novos-pontos (append novos-pontos (list novo-p)))))))))))

              (cond
                (erro-msg (list :erro erro-msg))
                ((not tem-alteracao) (list :sem-alteracoes pontos))
                (t
                 (setq novos-pontos (lp-recalcular-demandas-acumuladas novos-pontos))
                 (if (and (fboundp 'lp-clan-obter-ultimo-erro) (lp-clan-obter-ultimo-erro))
                   (list :erro (strcat "Falha no cálculo normativo LIGHT: " (lp-clan-obter-ultimo-erro)))
                   (progn
                     (setq update-res (vl-catch-all-apply 'lp-atualizar-celulas-tabela (list tbl-obj novos-pontos)))
                     (if (vl-catch-all-error-p update-res)
                       (list :erro (strcat "Erro ao atualizar tabela: " (vl-catch-all-error-message update-res)))
                       (progn (lp-db-salvar-pontos novos-pontos)
                              (list :atualizado novos-pontos pontos-afetados))))))))))))))

(defun lp-atualizar-exclusao-tabela (tbl-handle idx-excluido pontos / ent edata obj del-res row-idx)
  "Remove a linha do ponto excluído da tabela vinculada e renumera as demais."
  (if (and tbl-handle (setq ent (handent tbl-handle)))
    (progn
      (setq edata (entget ent))
      (if (and edata (listp edata) (= (cdr (assoc 0 edata)) "ACAD_TABLE"))
        (progn
          (setq obj (vl-catch-all-apply 'vlax-ename->vla-object (list ent)))
          (if (not (vl-catch-all-error-p obj))
            (progn
              (setq del-res (vl-catch-all-apply 'vla-DeleteRows (list obj (1+ idx-excluido) 1)))
              (if (not (vl-catch-all-error-p del-res))
                (progn
                  (setq row-idx 2)
                  (foreach p pontos
                    (if (< row-idx (vla-get-Rows obj))
                      (vla-SetText obj row-idx 0 (lp-format-val (cdr (assoc "SEQ" p)))))
                    (setq row-idx (1+ row-idx)))
                  (vla-Update obj)
                  (princ (strcat "\n[SINCRONISMO] Linha do ponto " (itoa idx-excluido)
                                 " removida da tabela vinculada.")))
                (princ "\n[AVISO] Não foi possível remover a linha diretamente da tabela.")))))
        (princ "\n[AVISO] Tabela vinculada não encontrada ou inválida no desenho."))))
  (princ))

;;; ----------------------------------------------------------------------------
;;; 9. REVISÃO E MANIPULAÇÃO DA COLETA
;;; ----------------------------------------------------------------------------

(defun lp-exibir-revisao (pontos / p seq poste ramais lum clientes pos cs dem acum coords)
  (textscr)
  (princ "\n==================================================================================================================================")
  (princ "\n                                          REVISÃO DE PONTOS COLETADOS - OXCAD                                                     ")
  (princ "\n==================================================================================================================================")
  (princ "\n PONTO | POSTE      | RAMAIS               | LUMINÁRIA   | CLI | POS | CS | DEMANDA (kVA) | ACUMULADA (kVA) | COORDENADAS           ")
  (princ "\n----------------------------------------------------------------------------------------------------------------------------------")
  (foreach p pontos
    (setq seq (lp-format-val (cdr (assoc "SEQ" p))) poste (lp-format-val (cdr (assoc "POSTE" p)))
          ramais (lp-format-val (cdr (assoc "RAMAIS" p))) lum (lp-format-val (cdr (assoc "LUM" p)))
          clientes (lp-format-val (cdr (assoc "CLIENTES" p))) pos (lp-format-val (cdr (assoc "POSICOES" p)))
          cs (lp-format-val (cdr (assoc "CS" p))) dem (lp-format-val (cdr (assoc "DEMANDA" p)))
          acum (lp-format-val (cdr (assoc "ACUMULADA" p)))
          coords (vl-string-translate "\n" " | " (lp-format-val (cdr (assoc "COORDENADAS" p)))))
    (princ (strcat "\n " seq (substr "    " 1 (max 1 (- 5 (strlen seq)))) " | " poste (substr "          " 1 (max 1 (- 10 (strlen poste))))
                   " | " ramais (substr "                    " 1 (max 1 (- 20 (strlen ramais)))) " | " lum (substr "           " 1 (max 1 (- 11 (strlen lum))))
                   " | " clientes (substr "   " 1 (max 1 (- 3 (strlen clientes)))) " | " pos (substr "   " 1 (max 1 (- 3 (strlen pos))))
                   " | " cs (substr "  " 1 (max 1 (- 2 (strlen cs)))) " | " dem (substr "             " 1 (max 1 (- 13 (strlen dem))))
                   " | " acum (substr "              " 1 (max 1 (- 14 (strlen acum)))) " | " coords)))
  (princ "\n==================================================================================================================================\n")
  (graphscr))

(defun lp-verificar-duplicidade (pontos novo-poste / ocorrencias)
  (setq ocorrencias '())
  (if (and (/= novo-poste "-") (/= novo-poste ""))
    (foreach p pontos
      (if (= (strcase (cdr (assoc "POSTE" p))) (strcase novo-poste))
        (setq ocorrencias (append ocorrencias (list (cdr (assoc "SEQ" p))))))))
  ocorrencias)

(defun lp-renumerar-pontos (pontos / idx)
  "Renumera sequencialmente os registros de 1 a N preservando todos os atributos originais."
  (setq idx 0)
  (mapcar '(lambda (p) (setq idx (1+ idx)) (if (assoc "SEQ" p) (subst (cons "SEQ" idx) (assoc "SEQ" p) p) (append p (list (cons "SEQ" idx))))) pontos))

(defun lp-excluir-ponto (pontos idx-alvo / i removido remanescentes)
  "Remove exatamente o ponto selecionado (1 a N) e renumera sequencialmente os restantes."
  (if (or (null pontos) (null idx-alvo) (< idx-alvo 1) (> idx-alvo (length pontos)))
    pontos
    (progn
      (setq i 0 removido nil remanescentes '())
      (foreach p pontos
        (setq i (1+ i))
        (if (and (not removido) (or (= (cdr (assoc "SEQ" p)) idx-alvo) (= i idx-alvo)))
          (setq removido t)
          (setq remanescentes (cons p remanescentes))))
      (lp-renumerar-pontos (reverse remanescentes)))))

(defun lp-precisa-renumerar-p (pontos / idx precisa)
  "Verifica se a lista de pontos necessita de normalização sequencial."
  (setq idx 0 precisa nil)
  (foreach p pontos (setq idx (1+ idx)) (if (/= (cdr (assoc "SEQ" p)) idx) (setq precisa t)))
  precisa)

;;; ----------------------------------------------------------------------------
;;; 10. COMANDO PRINCIPAL: LEVANTAR_POSTES (LP)
;;; ----------------------------------------------------------------------------

(defun c:LEVANTAR_POSTES (/ *error* old-pickadd pontos opt looping forcar-menu sel idx ent
                           raw-texts text-handles novo-ponto novo-poste dups
                           table-ok sel-blk coords tbl-handle sync-res opt-tabela
                           recriar pt-geom dig-id eh-passante)
  (vl-load-com)

  (defun *error* (msg)
    (if (numberp old-pickadd) (setvar "PICKADD" old-pickadd))
    (if (and msg (/= msg "Function cancelled") (/= msg "quit / exit abort"))
      (princ (strcat "\n[LEVANTAR_POSTES][ERRO] " msg)))
    (princ "\n[LEVANTAR_POSTES] Operação finalizada. Coleta preservada no DWG.")
    (princ))

  (setq old-pickadd (getvar "PICKADD"))
  (setvar "PICKADD" 2)

  (setq pontos (lp-db-obter-pontos))
  (if (lp-precisa-renumerar-p pontos)
    (progn
      (setq pontos (lp-renumerar-pontos pontos))
      (lp-db-salvar-pontos pontos)))

  ;; Sincronização automática na abertura do comando se houver tabela vinculada
  (setq tbl-handle (lp-db-obter-tabela-handle))
  (if (and tbl-handle (> (length pontos) 0))
    (progn
      (setq sync-res (lp-sincronizar-levantamento pontos tbl-handle))
      (cond
        ((= (car sync-res) :atualizado)
         (setq pontos (cadr sync-res))
         (princ (strcat "\n[LEVANTAR_POSTES][SINCRONISMO] Tabela (Handle #" tbl-handle
                        ") atualizada automaticamente. Ponto(s) alterado(s): "
                        (vl-prin1-to-string (caddr sync-res)) ".")))
        ((= (car sync-res) :sem-alteracoes)
         (princ (strcat "\n[LEVANTAR_POSTES][SINCRONISMO] Tabela (Handle #" tbl-handle
                        ") verificada: nenhuma alteração detectada nos textos.")))
        ((= (car sync-res) :tabela-inexistente)
         (princ (strcat "\n[AVISO][LEVANTAR_POSTES] A tabela vinculada (Handle #" tbl-handle
                        ") não foi encontrada no desenho (foi excluída)."))
         (princ "\n[LEVANTAR_POSTES] Os dados coletados foram preservados integralmente.")
         (initget "Sim Nao")
         (if (= (getkword "\nDeseja gerar uma nova tabela para os pontos existentes? [Sim/Nao] <Sim>: ") "Nao")
           (progn (lp-db-remover-tabela-handle) (setq tbl-handle nil)
                  (princ "\n[LEVANTAR_POSTES] Vínculo com tabela anterior removido."))
           (if (setq table-ok (lp-gerar-tabela-cad pontos))
             (progn (setq tbl-handle (lp-db-obter-tabela-handle))
                    (princ "\n[SUCESSO] Nova tabela gerada e vinculada ao levantamento.")))))
        ((= (car sync-res) :erro)
         (princ (strcat "\n[AVISO][LEVANTAR_POSTES] " (cadr sync-res)))
         (princ "\n[LEVANTAR_POSTES] Sincronização cancelada com segurança. Coleta preservada.")))))

  (setq looping t forcar-menu nil)

  (while looping
    (setq pontos (lp-db-obter-pontos))
    (if (lp-precisa-renumerar-p pontos)
      (progn
        (setq pontos (lp-renumerar-pontos pontos))
        (lp-db-salvar-pontos pontos)))
    (if (or (> (length pontos) 0) forcar-menu)
      (progn
        (setq forcar-menu nil)
        (princ (strcat "\n[LEVANTAR_POSTES] " (itoa (length pontos))
                       " ponto(s) na coleta. | Modo: "
                       (if (fboundp 'lp-clan-status-modo-str) (lp-clan-status-modo-str) (lp-db-obter-modo))))
        (if (and (fboundp 'lp-cqt-colunas-adicionais-p) (lp-cqt-colunas-adicionais-p))
          (initget "Adicionar Revisar Excluir Gerar Limpar Sair Configurar Excel")
          (initget "Adicionar Revisar Excluir Gerar Limpar Sair Configurar"))
        (setq opt (getkword (if (and (fboundp 'lp-cqt-colunas-adicionais-p) (lp-cqt-colunas-adicionais-p))
                              "\nOpção [Adicionar/Revisar/Excluir/Gerar/Excel/Configurar/Limpar/Sair] <Adicionar>: "
                              "\nOpção [Adicionar/Revisar/Excluir/Gerar/Configurar/Limpar/Sair] <Adicionar>: ")) )
        (if (null opt) (setq opt "Adicionar")))
      (setq opt "Adicionar"))

    (cond
      ;; OPÇÃO: CONFIGURAR MODO
      ((= opt "Configurar")
       (if (fboundp 'lp-configurar-modo) (lp-configurar-modo))
       (setq forcar-menu t))

      ;; OPÇÃO: ADICIONAR NOVO PONTO
      ((= opt "Adicionar")
       (princ (strcat "\nSelecione textos (TEXT/MTEXT) do Ponto "
                      (itoa (1+ (length pontos)))
                      " (Enter se for poste passante sem textos): "))
       (setq sel (ssget '((0 . "TEXT,MTEXT"))))
       (setq sel-blk nil coords "-" text-handles '() raw-texts '() novo-poste nil eh-passante nil)
       (if sel
         (progn
           (setq idx 0)
           (repeat (sslength sel)
             (setq ent (ssname sel idx)
                   raw-texts (append raw-texts (list (cdr (assoc 1 (entget ent))))))
             (setq text-handles (append text-handles (list (cdr (assoc 5 (entget ent))))))
             (setq idx (1+ idx)))

           ;; Seleção opcional do bloco poste / bloco CO
           (setq sel-blk (entsel "\nSelecione o bloco do poste / bloco CO (Enter se não houver): "))
           (setq coords (lp-extrair-coordenadas-bloco (if sel-blk (car sel-blk) nil)))
           (if (= coords "-")
             (princ "\n[AVISO] Bloco de coordenadas não selecionado ou inválido. Registrado como ausente (-).")
             (princ (strcat "\n[COORDENADAS] " (vl-string-translate "\n" " | " coords))))

           (setq novo-ponto (lp-process-point-texts raw-texts (1+ (length pontos)) coords))
           (setq novo-ponto (cons (cons "TEXT_HANDLES" text-handles) novo-ponto))
           (if sel-blk
             (setq novo-ponto (cons (cons "BLOCO_POSTE_HANDLE" (cdr (assoc 5 (entget (car sel-blk))))) novo-ponto)))
           (setq novo-poste (cdr (assoc "POSTE" novo-ponto)))
           (if (and (= (lp-db-obter-modo) "CLANDESTINO") (= novo-poste "-") (fboundp 'lp-clan-solicitar-poste-ponto))
             (progn
               (setq novo-poste (lp-clan-solicitar-poste-ponto))
               (setq novo-ponto (subst (cons "POSTE" novo-poste) (assoc "POSTE" novo-ponto) novo-ponto)))))
         (progn
           ;; Fluxo B: Poste Passante sem Textos
           (princ "\n[POSTE PASSANTE] Nenhum texto selecionado. Selecione o bloco ou clique no ponto do poste.")
           (setq sel-blk (entsel "\nSelecione o bloco do poste passante (ou Enter para indicar coordenada): "))
           (if sel-blk
             (progn
               (setq coords (lp-extrair-coordenadas-bloco (car sel-blk)))
               (if (= coords "-")
                 (princ "\n[AVISO] Bloco sem atributos N/E válidos. Coordenadas registradas como ausente (-).")
                 (princ (strcat "\n[COORDENADAS] " (vl-string-translate "\n" " | " coords)))))
             (progn
               (setq pt-geom (getpoint "\nClique no ponto geométrico do poste (Enter para cancelar cadastro): "))
               (if pt-geom
                 (setq coords (strcat "N: " (rtos (cadr pt-geom) 2 2) "\nE: " (rtos (car pt-geom) 2 2)))
                 (setq coords nil))))
           (if (null coords)
             (princ "\n[LEVANTAR_POSTES] Cadastro cancelado. Nenhum ponto ou bloco informado.")
             (progn
               (setq dig-id (getstring t "\nDigite o identificador do poste passante (ex: P5) [Enter para cancelar]: "))
               (setq dig-id (strcase (lp-trim dig-id)))
               (if (= dig-id "")
                 (princ "\n[LEVANTAR_POSTES] Identificador não informado. Cadastro do poste passante cancelado.")
                 (progn
                   (setq eh-passante t
                         novo-poste dig-id
                         novo-ponto (list (cons "SEQ" (1+ (length pontos)))
                                          (cons "POSTE" novo-poste)
                                          (cons "RAMAIS" "-")
                                          (cons "LUM" "-")
                                          (cons "CLIENTES" 0)
                                          (cons "POSICOES" "-")
                                          (cons "CS" "-")
                                          (cons "DEMANDA" (if (= (lp-db-obter-modo) "CLANDESTINO") "0,00" "0.00"))
                                          (cons "ACUMULADA" (if (= (lp-db-obter-modo) "CLANDESTINO") "0,00" "0.00"))
                                          (cons "COORDENADAS" coords)
                                          (cons "RAW" '())
                                          (cons "PASSANTE" "SIM")
                                          (cons "TEXT_HANDLES" '())))
                   (if sel-blk
                     (setq novo-ponto (cons (cons "BLOCO_POSTE_HANDLE" (cdr (assoc 5 (entget (car sel-blk))))) novo-ponto)))))))))

       (if (and novo-ponto novo-poste (/= novo-poste "-") (/= novo-poste ""))
         (progn
           ;; Detecção de duplicidade informativa
           (setq dups (lp-verificar-duplicidade pontos novo-poste))
           (if (> (length dups) 0)
             (princ (strcat "\n[AVISO] Poste " novo-poste " já coletado no(s) ponto(s): "
                            (vl-prin1-to-string dups) ". Registrado como nova ocorrência.")))

           (setq pontos (append pontos (list novo-ponto)))
           (setq pontos (lp-recalcular-demandas-acumuladas pontos))
           (lp-db-salvar-pontos pontos)
           (setq novo-ponto (last pontos))

           ;; Feedback resumido ao usuário (após cálculo da demanda acumulada e CQT)
           (princ (strcat "\n[PONTO " (lp-format-val (cdr (assoc "SEQ" novo-ponto))) "]"
                          (if eh-passante " [PASSANTE]" "")
                          " Poste: " novo-poste " | Ramais: " (lp-format-val (cdr (assoc "RAMAIS" novo-ponto)))
                          " | Clientes: " (lp-format-val (cdr (assoc "CLIENTES" novo-ponto)))
                          " | Dem: " (lp-format-val (cdr (assoc "DEMANDA" novo-ponto)))
                          " | Acum: " (lp-format-val (cdr (assoc "ACUMULADA" novo-ponto)))
                          (if (and (= (lp-db-obter-modo) "CLANDESTINO") (assoc "CQT_PREVISTO" novo-ponto))
                            (strcat " | Cabo: " (lp-format-val (cdr (assoc "CONDUTOR_PREVISTO" novo-ponto)))
                                    " | CQT: " (lp-format-val (cdr (assoc "CQT_PREVISTO" novo-ponto))))
                            ""))))
         (setq forcar-menu t)))

      ;; OPÇÃO: REVISAR PONTOS
      ((= opt "Revisar")
       (if (> (length pontos) 0)
         (lp-exibir-revisao pontos)
         (princ "\nNenhum ponto registrado para revisão.")))

      ;; OPÇÃO: EXCLUIR PONTO
      ((= opt "Excluir")
       (if (> (length pontos) 0)
         (progn
           (initget 6)
           (setq idx (getint (strcat "\nNúmero do ponto a excluir (1 a "
                                     (itoa (length pontos)) "): ")))
           (if (and idx (>= idx 1) (<= idx (length pontos)))
             (progn
               (setq pontos (lp-excluir-ponto pontos idx))
               (lp-db-salvar-pontos pontos)
               (setq tbl-handle (lp-db-obter-tabela-handle))
               (if tbl-handle
                 (lp-atualizar-exclusao-tabela tbl-handle idx pontos))
               (princ "\nPonto removido e sequência atualizada."))
             (princ "\nNúmero de ponto inválido.")))
         (princ "\nNenhum ponto para excluir.")))

      ;; OPÇÃO: GERAR TABELA
      ((= opt "Gerar")
       (if (> (length pontos) 0)
         (progn
           (setq tbl-handle (lp-db-obter-tabela-handle)
                 recriar t)
           (if (and tbl-handle (handent tbl-handle))
             (progn
               (princ (strcat "\n[AVISO] Já existe uma tabela vinculada (Handle #" tbl-handle ")."))
               (initget "Atualizar Nova Cancelar")
               (setq opt-tabela (getkword "\nOpção [Atualizar/Nova/Cancelar] <Atualizar>: "))
               (if (null opt-tabela) (setq opt-tabela "Atualizar"))
               (cond
                 ((= opt-tabela "Atualizar")
                  (setq recriar nil)
                  (setq sync-res (lp-sincronizar-levantamento pontos tbl-handle))
                  (if (member (car sync-res) '(:atualizado :sem-alteracoes))
                    (progn
                      (princ (strcat "\n[SUCESSO] Tabela existente (Handle #" tbl-handle ") atualizada."))
                      (setq looping nil))
                    (princ (strcat "\n[AVISO] " (vl-prin1-to-string (cadr sync-res))))))
                 ((= opt-tabela "Cancelar")
                  (setq recriar nil)
                  (princ "\nGeração cancelada. Coleta mantida."))
                 (t (setq recriar t)))))
           (if recriar
             (progn
               (setq table-ok (lp-gerar-tabela-cad pontos))
               (if table-ok
                 (progn
                   (lp-db-salvar-pontos pontos)
                   (princ "\n[SUCESSO] Tabela gerada e vinculada ao levantamento no DWG.")
                   (setq looping nil))
                 (princ "\nA tabela não foi criada. A coleta foi preservada.")))))
         (princ "\nNenhum ponto para gerar tabela.")))

      ;; OPÇÃO: EXPORTAR EXCEL
      ((= opt "Excel")
       (if (and pontos (> (length pontos) 0))
         (if (fboundp 'lp-cqt-exportar-excel)
           (lp-cqt-exportar-excel (lp-recalcular-demandas-acumuladas pontos))
           (princ "\n[AVISO] Módulo de exportação CQT não disponível."))
         (princ "\n[AVISO] Nenhum ponto coletado para exportar.")))

      ;; OPÇÃO: LIMPAR EXPLICITAMENTE
      ((= opt "Limpar")
       (initget "Sim Nao")
       (if (= (getkword "\nDeseja realmente descartar todos os pontos coletados? [Sim/Nao] <Nao>: ") "Sim")
         (progn
           (lp-db-limpar-pontos) (lp-db-remover-tabela-handle) (setq pontos '() looping nil)
           (princ "\nColeta descartada e vínculo com tabela removido."))
         (princ "\nLimpeza cancelada.")))

      ;; OPÇÃO: SAIR / PAUSAR
      ((= opt "Sair")
       (princ "\nColeta mantida no DWG para continuação posterior.")
       (setq looping nil))))

  (if (numberp old-pickadd) (setvar "PICKADD" old-pickadd))
  (princ))

(defun c:LP () (c:LEVANTAR_POSTES))
(princ "\n[LEVANTAMENTO] Módulo de Postes carregado. Use LEVANTAR_POSTES ou LP.")
(princ)
